# -*- coding: utf-8 -*-

import FreeCAD
import Spreadsheet
import Draft
import os
import re
import time
from git import Repo

FontFile=os.path.dirname(os.path.realpath(__file__))+"/blackout-font/Blackout Midnight.ttf"
Size=3
Spacing=4
Tracking=1.5
Scale=0.3

doc = FreeCAD.ActiveDocument
docDir, docFilename = os.path.split(doc.FileName)

# assert os.path.isdir(docDir)
repo = Repo(docDir)
assert repo.__class__ is Repo
assert not repo.bare

remote=list(repo.remotes.origin.urls)[0].replace("git@","").replace("github.com:","").replace(".git","")

if repo.head.is_detached:
    branch=repo.commit().name_rev.split()[1]
else:
    branch=repo.active_branch.name

commit=repo.head.commit
rev=commit.hexsha[:8]
date=time.strftime("%Y–%m–%d", time.gmtime(commit.committed_date))
if repo.is_dirty():
    dirty="*"
else:
    dirty=""

sheet=doc.getObject('PartInfo')
if not sheet:
    sheet=doc.addObject('Spreadsheet::Sheet','PartInfo')
    sheet.set('A1', 'Part Info')
    sheet.set('B1', 'alias')
nameAddress=sheet.getCellFromAlias('name')
if not nameAddress:
    sheet.set('A2', 'Name')
    sheet.set('B2', 'name')
    sheet.setAlias('C2', 'name')
    nameAddress=sheet.getCellFromAlias('name')
sheet.set(nameAddress, docFilename)
repoAddress=sheet.getCellFromAlias('repo')
if not repoAddress:
    sheet.set('A3', 'Repo')
    sheet.set('B3', 'repo')
    sheet.setAlias('C3', 'repo')
    repoAddress=sheet.getCellFromAlias('repo')
sheet.set(repoAddress, remote)
branchAddress=sheet.getCellFromAlias('branch')
if not branchAddress:
    sheet.set('A4', 'Branch')
    sheet.set('B4', 'branch')
    sheet.setAlias('C4', 'branch')
    branchAddress=sheet.getCellFromAlias('branch')
sheet.set(branchAddress, branch + dirty)
commitAddress=sheet.getCellFromAlias('commit')
if not commitAddress:
    sheet.set('A5', 'Commit')
    sheet.set('B5', 'commit')
    sheet.setAlias('C5', 'commit')
    commitAddress=sheet.getCellFromAlias('commit')
sheet.set(commitAddress, rev)
dateAddress=sheet.getCellFromAlias('date')
if not dateAddress:
    sheet.set('A6', 'Date')
    sheet.set('B6', 'date')
    sheet.setAlias('C6', 'date')
    dateAddress=sheet.getCellFromAlias('date')
sheet.set(dateAddress, date)

plm=FreeCAD.Placement()
scale=FreeCAD.Vector(Scale,Scale,Scale)

ss1=Draft.makeShapeString(String=docFilename,FontFile=FontFile,Size=Size,Tracking=Tracking)
plm.Base=FreeCAD.Vector(0.0,0.0,0.0)
ss1.Placement=plm
ss1.Support=None
Draft.autogroup(ss1)
sss1=Draft.scale([ss1],scale=scale,center=FreeCAD.Vector(0.0,0.0,0.0),copy=False)
sss1.Placement=plm
#doc.removeObject(ss1.Name)

ss2=Draft.makeShapeString(String=remote,FontFile=FontFile,Size=Size,Tracking=Tracking)
plm.Base=FreeCAD.Vector(0.0,-Size*Spacing,0.0)
ss2.Placement=plm
ss2.Support=None
Draft.autogroup(ss2)
sss2=Draft.scale([ss2],scale=scale,center=FreeCAD.Vector(0.0,0.0,0.0),copy=False)
sss2.Placement=plm
#doc.removeObject(ss2.Name)

ss3=Draft.makeShapeString(String=branch + dirty,FontFile=FontFile,Size=Size,Tracking=Tracking)
plm.Base=FreeCAD.Vector(0.0,-Size*Spacing*2.0,0.0)
ss3.Placement=plm
ss3.Support=None
Draft.autogroup(ss3)
sss3=Draft.scale([ss3],scale=scale,center=FreeCAD.Vector(0.0,0.0,0.0),copy=False)
sss3.Placement=plm
#doc.removeObject(ss3.Name)

ss4=Draft.makeShapeString(String=rev + " " + date,FontFile=FontFile,Size=Size,Tracking=Tracking)
plm.Base=FreeCAD.Vector(0.0,-Size*Spacing*3.0,0.0)
ss4.Placement=plm
ss4.Support=None
Draft.autogroup(ss4)
sss4=Draft.scale([ss4],scale=scale,center=FreeCAD.Vector(0.0,0.0,0.0),copy=False)
sss4.Placement=plm
#doc.removeObject(ss4.Name)

if doc.getObject("PartInfoBaseSketch"):
    doc.removeObject("PartInfoBaseSketch")

pis=Draft.makeSketch([sss1,sss2,sss3,sss4],name="PartInfoBaseSketch")

for obj in doc.findObjects('Sketcher::SketchObject'):
    if re.search("^PartInfoSketch.*",obj.Label):
        obj.deleteAllGeometry()
        obj.carbonCopy(pis.Name,False)

App.ActiveDocument.recompute()
